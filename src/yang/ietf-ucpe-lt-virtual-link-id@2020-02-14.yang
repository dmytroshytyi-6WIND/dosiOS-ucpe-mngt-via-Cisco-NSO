module ietf-ucpe-lt-virtual-link-id {
  yang-version 1.1;
  namespace "urn:ietf:params:xml:ns:yang:ietf-ucpe-lt-virtual-link-id";
	prefix lt-vlink-id;
	import ietf-network{
		prefix nw;
		reference
	    "RFC 8345: YANG Data Model for Network Topologies";

	}
  import ietf-te-topology {
    prefix "tet";
    reference
      "I-D.ietf-teas-yang-te-topo: YANG Data Model for Traffic
       Engineering (TE) Topologies";
  }
	import ietf-te-topology-sf{
		prefix "tet-sf";
		reference "RFC XXXX: SF Aware TE Topology YANG Model";
	}
  organization
    "SFR";
  contact
    "Dmytro Shytyi
     EMail:ietf.dmytro@shytyi.net";
  description
    "This is a YANG data model that extends link-termination of
		 service function vith virtual link.

     Copyright (c) 2019 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2020-02-14 {
    description
      "Added virtual link id";
    reference
      "draft-shytyi-opsawg-vysm-08";
  }
  augment "/nw:networks/nw:network/nw:node/tet:te/"
    + "tet:te-node-attributes/tet-sf:service-function/"
    + "tet-sf:link-terminations/tet-sf:link-termination"{

    	leaf virtual-link-id {
				type string;
					description 
						"Virtual link id between equipment and service function";
				}	
		
    		description
						"Virtual link id between equipment and service function";
			}
}
